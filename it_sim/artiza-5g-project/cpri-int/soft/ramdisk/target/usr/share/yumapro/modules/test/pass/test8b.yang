submodule test8b {

    belongs-to test8 { prefix t8; }

    include test8a;
    include test8c;

    revision 2011-02-04 {
        description "Initial revision.";
    }

    augment /top {
       leaf a {
         type leafref { path /top/b; }
       }
    }

}
