module test-types {
    namespace "http://netconfcentral.org/ns/test-types";

    prefix "tt";

    organization
        "Netconf Central";

    contact
        "Andy Bierman";

    description
        "YANG types test module";

    revision "2017-10-04";

    typedef season-enum {
        type enumeration {
            enum spring;
            enum summer;
            enum fall;
            enum winter;
        }
    }
    typedef bits-type {
       type bits {
           bit zero;
           bit one;
           bit two {
               position 2;
           }
           bit after_two;
            bit four;
            bit five;
            bit six;
            bit seven;
            bit eight;
            bit nine;
            bit ten;
            bit alpha;
            bit beta;
            bit charlie;
            bit delta;
            bit echo;
            bit foxtrot;
            bit golf;
            bit hotel;
            bit india;
            bit juliett;
            bit kilo;
            bit lima;
            bit mike;
            bit november;
            bit oscar;
            bit papa;
            bit quebec;
            bit romeo;
            bit sierra;
            bit tango;
            bit uniform;
            bit victor;
            bit whiskey;
            bit xray;
            bit yankee;
            bit zulu;
        }
    }

    identity id;

    identity id1 {
        base id;
    }

    identity id2 {
        base id;
    }

    identity id3 {
        base id;
    }

    identity id2.1 {
        base id2;
    }

    identity id2.2 {
        base id2;
    }

    typedef id-type {
        type identityref {
            base id;
        }
        description "Basic type is identityref(id1 id2 id2.1 id2.2 id3)";
    }

    grouping all-type-leaves {
        leaf int8-leaf {
            type int8;
        }
        leaf int16-leaf {
            type int16;
        }
        leaf int32-leaf {
            type int32;
        }
        leaf int64-leaf {
            type int64;
        }
        leaf uint8-leaf {
            type uint8;
        }
        leaf uint16-leaf {
            type uint16;
        }
        leaf uint32-leaf {
            type uint32;
        }
        leaf uint64-leaf {
            type uint64;
        }
        leaf decimal64-leaf {
            type decimal64 {
                fraction-digits 2;
            }
        }
        leaf string-leaf {
            type string;
        }
        leaf boolean-leaf {
            type boolean;
        }
        leaf enumeration-leaf {
            type season-enum;
        }
        leaf bits-leaf {
            type bits-type;
        }
        leaf binary-leaf {
            type binary;
        }
        leaf identityref-leaf {
            type id-type;
        }
        leaf empty-leaf {
            type empty;
        }
    }

    grouping all-type-leaf-lists {
        leaf-list int8-leaflist {
            type int8;
        }
        leaf-list int16-leaflist {
            type int16;
        }
        leaf-list int32-leaflist {
            type int32;
        }
        leaf-list int64-leaflist{
            type int64;
        }
        leaf-list uint8-leaflist {
            type uint8;
        }
        leaf-list uint16-leaflist {
            type uint16;
        }
        leaf-list uint32-leaflist {
            type uint32;
        }
        leaf-list uint64-leaflist {
            type uint64;
        }
        leaf-list decimal64-leaflist {
            type decimal64 {
                fraction-digits 2;
            }
        }
        leaf-list string-leaflist {
            type string;
        }
        leaf-list boolean-leaflist {
            type boolean;
        }
        leaf-list enumeration-leaflist {
            type season-enum;
        }
        leaf-list bits-leaflist {
            type bits-type;
        }
        leaf-list binary-leaflist {
            type binary;
        }
        leaf-list identityref-leaflist {
            type id-type;
        }
    }


    grouping all-type-union-leaf {

        leaf union-leaf-int8 {
            type union {
                type int8;
                type string;
            }
        }

        leaf union-leaf-int16 {
            type union {
                type int16;
                type string;
            }
        }

        leaf union-leaf-int32 {
            type union {
                type int32;
                type string;
            }
        }

        leaf union-leaf-int64 {
            type union {
                type int64;
                type string;
            }
        }

        leaf union-leaf-uint8 {
            type union {
                type uint8;
                type string;
            }
        }

        leaf union-leaf-uint16 {
            type union {
                type uint16;
                type string;
            }
        }

        leaf union-leaf-uint32 {
            type union {
                type uint32;
                type string;
            }
        }


        leaf union-leaf-uint64 {
            type union {
                type uint64;
                type string;
            }
        }

        leaf union-leaf-decimal64 {
            type union {
                type decimal64 {fraction-digits 8;}
                type string;
            }
        }

        leaf union-leaf-enumeration {
            type union {
                type enumeration {
                    enum one;
                    enum two;
                    enum three;
                }
                type string;
            }
        }

        leaf union-leaf-bits {
            type union {
                type bits {
                    bit alpha;
                    bit beta;
                    bit gamma;
                }
                type string;
            }
        }

        leaf union-leaf-identityref {
            type union {
                type id-type;
                type string;
            }
        }

        leaf union-leaf-binary {
            type union {
                type binary {
                    length "3";
                }
                type string;
            }
        }

        leaf union-leaf-boolean {
            type union {
                type boolean;
                type string;
            }
        }

        leaf union-leaf-string {
            type union {
                type string;
                type decimal64 {fraction-digits 8;}

            }
        }
    }

    grouping all-type-union-leaflist {

        leaf-list union-leaflist1 {
            type union {
                type boolean;
                type uint64;
                type int64;
                type id-type;
                type decimal64 {fraction-digits 8;}
                type enumeration {
                    enum red;
                    enum blue;
                    enum voilet;
                }
                type bits {
                    bit zero;
                    bit one;
                }
                type string;
            }
        }

        leaf-list union-leaflist-integer8 {
            type union{
                type uint8;
                type int8;
            }
        }

        leaf-list union-leaflist-integer16 {
            type union{
                type uint16;
                type int16;
            }
        }

        leaf-list union-leaflist-integer32 {
            type union{
                type uint32;
                type int32;
            }
        }

        leaf-list union-leaflist-binary {
            type union{
                type binary;
                type int32;
            }
        }
    }

    container config-nodes {
        uses all-type-leaves;
        uses all-type-leaf-lists;
        uses all-type-union-leaf;
        uses all-type-union-leaflist;
        leaf set-defaults {
            type boolean;
        }
    }

    list test-leaf-ref-union {

        key 'leaf-ref-key';
        leaf leaf-ref-key {
            type leafref {
                path "/config-nodes/union-leaf-int8";
            }
        }
    }

    list test-leaf-ref-iref {
        key 'i-ref-key';
        leaf i-ref-key {
            type leafref {
                path "/config-nodes/identityref-leaf";
            }
        }
    }

    list order-list {
        description "For testing ordered by user for list";
        ordered-by user;
        key "uint8-leaf uint16-leaf";
        leaf uint16-leaf { type uint16; }
        leaf uint8-leaf{ type uint8; }
    }

    container order-test {
        leaf-list order-leaflist{
            type uint8;
            ordered-by user;
        }
    }

    container edit-choice-nested {
        choice test-nested-choice {
            case A {
                leaf a1 {type string;}
                leaf a2 {type string;}
            }
            container B {
                choice B0 {
                    case B01 {
                        leaf b01 {type string;}
                    }
                      case B02 {
                        leaf b02 {type string;}
                    }
                }
            }
        }
    }

}
