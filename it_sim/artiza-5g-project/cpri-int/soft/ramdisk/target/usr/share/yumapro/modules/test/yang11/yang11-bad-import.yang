module yang11-bad-import {

  yang-version 1.1;
  namespace "http://netconfcentral.org/ns/yang11-bad-import";
  prefix ybim;

  import ietf-inet-types {
    prefix inet;
    revision-date 2010-09-24;
    description "first revision of INET types";
    reference "RFC 6021";
  }

  import ietf-inet-types {
    prefix inet2;
    revision-date 2013-07-15;
    description "second revision of INET types";
    reference "RFC 6991";
  }

  import ietf-inet-types {
    prefix inet3;
  }

  import ietf-yang-types {
    prefix inet3;
  }

  revision "2016-11-22";


  leaf A1 { type inet:ip-address; }

  leaf A2 { type inet2:ip-address; }

  leaf A3 { type inet3:ip-address; }

}
