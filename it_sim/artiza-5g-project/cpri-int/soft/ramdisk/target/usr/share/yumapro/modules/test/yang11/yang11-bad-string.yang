module yang11-bad-string {

  yang-version 1.1;
  namespace "http://netconfcentral.org/ns/yang11-bad-string";
  prefix ybadst;
  revision "2016-01-22" {
  }


   container mgmt-interface {
     leaf name {
        must "count(/interface[re-match(name, 'eth0\.\d+')])";
        type string;
     }
     leaf type {
       type string;
       must 'deref(.)/../enabled = "true"' {
         error-message
           "The management interface cannot be disabled.";
       }
       must 'deref(/inst-id)/enabled = "true"' {
         error-message
           "Test2 management interface cannot be disabled.";
       }

     }
   }

}
