module yang11-state-leafref-bad {
  yang-version 1.1;
  namespace "http://netconfcentral.org/ns/yang11-state-leafref-bad";
  prefix "ystate-bad";
  revision 2017-02-03;

  container A {
    leaf AA {
      type leafref {
        path "/A-state/AAA";
        require-instance true;
      }
    }
  }

  container A-state {
    config false;
    leaf AAA {
      type int32;
    }
  }


}
