module yumaworks-server {

    namespace "http://yumaworks.com/ns/yumaworks-server";

    prefix "yser";

    import ietf-netconf-acm { prefix nacm; }

    import netconfd-pro { prefix ndpro; }

    import yumaworks-extensions { prefix ywx; }

    organization "YumaWorks, Inc.";

    contact
        "Support <support at yumaworks.com>";

    description
       "Runtime access to netconfd-pro server parameters.
        The following parameters can be changed at run-time
        and the new value will be activated immediately.

        * allowed-user
        * eventlog-size
        * hello-timeout
        * idle-timeout
        * log-level
        * max-burst
        * max-cli-sessions
        * max-getbulk
        * max-sessions
        * subsys-timeout

        The rest of the CLI parameters can be edited for
        activation at the next reboot.

        If the server has write permission to the
        configuration file (e.g., netconfd-pro.conf) then
        the parameters will be saved when the server exits.


     Copyright (c) 2017 - 2018, YumaWorks, Inc. All rights reserved.

     Redistribution and use in source and binary forms, with or
     without modification, is permitted pursuant to, and subject
     to the license terms contained in, the BSD 3-Clause License
     http://opensource.org/licenses/BSD-3-Clause";

    revision 2018-04-21 {
        description
          "Add no-nvstore to server";
    }

    revision 2017-12-30 {
        description
          "Initial version";
    }

    container server {
      description
        "Runtime access to netconfd-pro CLI parameters for
         immediate change or activate-on-restart";
      nacm:default-deny-all;
      ywx:no-nvstore;
      uses ndpro:netconfd-pro-parms;
    }

}
