module yang11-default {

  yang-version 1.1;
  namespace "http://netconfcentral.org/ns/yang11-default";
  prefix ydef;
  revision "2016-04-18" {
  }

  leaf-list def-A {
    type int32 {}
    default 10;
    default 20;
    default 30;
  }

  leaf def-B {
    type int32;
    default 42;
  }

  uses grp-1 {
    refine def-C {
      default 1;
      default 100;
      default 42;
    }
  }

  grouping grp-1 {
    leaf-list def-C {
      type int32;
    }
  }

}
