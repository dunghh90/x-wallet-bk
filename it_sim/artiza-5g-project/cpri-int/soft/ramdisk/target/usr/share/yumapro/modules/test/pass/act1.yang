module act1 {
  yang-version 1.1;
  namespace "http://netconfcentral.org/ns/act1";
  prefix a;
  revision "2017-10-14";

  container objs {
   config false;
   list obj {
     key "idx";
     leaf idx { type int32; }
     leaf col1 { type string; }
     action draw {
       description "Draw this object";
       input {
         leaf i { type uint32; mandatory true; }
         leaf j { type uint32; }
       }
     }
    }
  }
}
