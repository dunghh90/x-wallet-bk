module testrev {

    namespace "http://netconfcentral.org/ns/testrev";
    prefix "trev";

    import testr1 {
        prefix r1;
        revision-date 2009-01-01;
    }

    import testr2 {
        prefix r2;
        revision-date 2009-01-01;
    }

    organization
        "Netconf Central";

    contact
        "Andy Bierman";

    description
        "YANG import-by-revision test module.";

    revision 2009-02-20 {
        description "Initial version.";
    }

    container foo {
      uses r1:TestGroup1;
    }

    container bar {
      uses r2:TestGroup;
    }

    leaf baz {
      type r2:TestType {
        range 2..max;
      }
    }

}
