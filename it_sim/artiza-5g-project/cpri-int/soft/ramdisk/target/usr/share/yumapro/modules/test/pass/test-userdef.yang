module test-userdef {
    yang-version 1.1;
    namespace "http://netconfcentral.org/ns/test-userdef";
    prefix "tud";

    import ietf-inet-types { prefix inet; }
    import ietf-yang-types { prefix yang; }

    revision 2018-07-23 {
        description "Test module of leafrefs using inet-inet-types.
            -YPW-1278:  leafref to ipv6, canonical value conversion problem";
    }

    revision 2018-04-08;

    grouping userdef-group {
        leaf t-ip-address { type inet:ip-address; }
        leaf t-ipv4-address { type inet:ipv4-address; }
        leaf t-ipv6-address { type inet:ipv6-address; }
        leaf t-ipv4-address-no-zone { type inet:ipv4-address-no-zone; }
        leaf t-ipv6-address-no-zone { type inet:ipv6-address-no-zone; }
        leaf t-domain-name { type inet:domain-name; }
        leaf t-uri { type inet:uri; }
        leaf-list t-ipv6-prefix { type inet:ipv6-prefix; }
    }

    grouping userdef-group2 {
        container leaflists {
            leaf-list t-ip-address { type inet:ip-address; }
            leaf-list t-ipv4-address { type inet:ipv4-address; }
            leaf-list t-ipv6-address { type inet:ipv6-address; }
            leaf-list t-ipv4-address-no-zone { type inet:ipv4-address-no-zone; }
            leaf-list t-ipv6-address-no-zone { type inet:ipv6-address-no-zone; }
            leaf-list t-domain-name { type inet:domain-name; }
            leaf-list t-uri { type inet:uri; }
            leaf-list t-ipv6-prefix { type inet:ipv6-prefix; }
        }
        container leaflists2 {
            leaf-list t-phys-address { type yang:phys-address; }
            leaf-list t-mac-address { type yang:mac-address; }
            leaf-list t-hex-string { type yang:hex-string; }
            leaf-list t-uuid { type yang:uuid; }
        }
    }

    container userdef {
      uses userdef-group;
      uses userdef-group2;
    }

    container ipv6 {
        container addresses {
            list address {
                key "ip";

                leaf ip {
                    type leafref {
                        path "../config/ip";
                    }
                }
                container config {
                    uses ipv6-address-config;
                }
            }
        }
    }

    grouping ipv6-address-config {
        leaf ip {
            type inet:ipv6-address-no-zone;
        }
        leaf prefix-length {
            type uint8 {
                range "0..128";
            }
            mandatory true;
        }
    }

}
