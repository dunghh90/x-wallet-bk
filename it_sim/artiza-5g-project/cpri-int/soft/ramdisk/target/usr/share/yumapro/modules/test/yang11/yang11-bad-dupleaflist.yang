module yang11-bad-dupleaflist {

  yang-version 1.1;
  namespace "http://netconfcentral.org/ns/yang11-bad-dupleaflist";
  prefix ybaddupll;
  revision "2016-11-22";

  leaf-list A {
    type int8;
    default 0;
    default 10;
    default 0;
  }

}
