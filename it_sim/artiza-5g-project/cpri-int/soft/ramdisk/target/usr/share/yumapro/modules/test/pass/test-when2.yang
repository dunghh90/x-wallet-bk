module test-when2 {
  namespace "http://www.yumaworks.com/ns/test-when2";
  prefix twhen2;

  revision "2019-05-22";

  typedef DisplayString {
    type string {
      length "0 .. 255";
    }
  }

  container when-test-container {
    presence
      "...";

    leaf toasterManufacturer {
      type DisplayString;
      config false;
      mandatory true;
    }

    leaf toasterModelNumber {
      type DisplayString;
      config false;
      mandatory true;
    }

    leaf toasterStatus {
      type enumeration {
        enum up {
          value 1;
        }
        enum down {
          value 2;
        }
      }
      config false;
      mandatory true;
    }

    leaf toasterWeight {
      type int32 {
        range "1 .. 10";
      }
      config true;
      default 5;
    }

    leaf A1 {
      type int32 {
        range "1 .. 10";
      }
      config true;
      default 8;
    }

    leaf b1 {
      when "../toasterWeight = 10";
      type int32 {
        range "1 .. 10";
      }
      config true;
      default 5;
    }
    leaf A2 {
      when "../toasterWeight <= 5";
      type int32 {
        range "1 .. 10";
      }
      config true;
      default 5;
    }
    leaf A01 {
      when "../toasterWeight = 8";
      type int32 {
        range "1 .. 10";
      }
      config true;
      default 5;
    }
  }
}
