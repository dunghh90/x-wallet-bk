/*
 * This module has been generated by smidump 0.4.8:
 *
 *      smidump -f yang --yang-smi-extensions SNMP-FRAMEWORK-MIB
 *
 * Do not edit. Edit the source file instead!
 */

module SNMP-FRAMEWORK-MIB {

   /*** NAMESPACE / PREFIX DEFINITION ***/

   namespace "urn:ietf:params:xml:ns:yang:smiv2:SNMP-FRAMEWORK-MIB";
   prefix "snmp-framework";

   /*** LINKAGE (IMPORTS / INCLUDES) ***/

   import yang-smi { prefix "smi"; }

   /*** META INFORMATION ***/

   organization
     "SNMPv3 Working Group";

   contact
     "WG-EMail:   snmpv3@lists.tislabs.com
      Subscribe:  snmpv3-request@lists.tislabs.com

      Co-Chair:   Russ Mundy
                  Network Associates Laboratories
      postal:     15204 Omega Drive, Suite 300
                  Rockville, MD 20850-4601
                  USA
      EMail:      mundy@tislabs.com
      phone:      +1 301-947-7107

      Co-Chair &
      Co-editor:  David Harrington
                  Enterasys Networks
      postal:     35 Industrial Way
                  P. O. Box 5005
                  Rochester, New Hampshire 03866-5005
                  USA
      EMail:      dbh@enterasys.com
      phone:      +1 603-337-2614

      Co-editor:  Randy Presuhn
                  BMC Software, Inc.
      postal:     2141 North First Street
                  San Jose, California 95131
                  USA
      EMail:      randy_presuhn@bmc.com
      phone:      +1 408-546-1006

      Co-editor:  Bert Wijnen
                  Lucent Technologies
      postal:     Schagen 33
                  3461 GL Linschoten
                  Netherlands

      EMail:      bwijnen@lucent.com
      phone:      +31 348-680-485
        ";

   description
     "The SNMP Management Architecture MIB

      Copyright (C) The Internet Society (2002). This
      version of this MIB module is part of RFC 3411;
      see the RFC itself for full legal notices.";

   revision "2002-10-14" {
      description
        "Changes in this revision:
         - Updated various administrative information.
         - Corrected some typos.
         - Corrected typo in description of SnmpEngineID
           that led to range overlap for 127.
         - Changed '255a' to '255t' in definition of
           SnmpAdminString to align with current SMI.
         - Reworded 'reserved' for value zero in
           DESCRIPTION of SnmpSecurityModel.
         - The algorithm for allocating security models
           should give 256 per enterprise block, rather
           than 255.
         - The example engine ID of 'abcd' is not
           legal. Replaced with '800002b804616263'H based
           on example enterprise 696, string 'abc'.
         - Added clarification that engineID should
           persist across re-initializations.
         This revision published as RFC 3411.";
   }
   revision "1999-01-19" {
      description
        "Updated editors' addresses, fixed typos.
         Published as RFC 2571.";
   }
   revision "1997-11-20" {
      description
        "The initial version, published in RFC 2271.";
   }

   /*** TYPE DEFINITIONS ***/

   typedef SnmpEngineID {
      type binary {
         length "5..32";
      }
   }

   typedef SnmpSecurityModel {
      type int32 {
         range "0..2147483647";
      }
   }

   typedef SnmpMessageProcessingModel {
      type int32 {
         range "0..2147483647";
      }
   }

   typedef SnmpSecurityLevel {
      type enumeration {
         enum noAuthNoPriv { value 1; }
         enum authNoPriv   { value 2; }
         enum authPriv     { value 3; }
      }
   }

   typedef SnmpAdminString {
      type string {
         length "0..255";
         pattern ".{0,255}";
      }
      smi:display-hint "255t";
   }

   container snmpEngine {

      config false;

      leaf snmpEngineID {
         type snmp-framework:SnmpEngineID;
         description
           "An SNMP engine's administratively-unique identifier.

            This information SHOULD be stored in non-volatile
            storage so that it remains constant across
            re-initializations of the SNMP engine.";
         smi:oid "1.3.6.1.6.3.10.2.1.1";
      }

      leaf snmpEngineBoots {
         type int32 {
            range "1..2147483647";
         }
         description
           "The number of times that the SNMP engine has
            (re-)initialized itself since snmpEngineID
            was last configured.";
         smi:oid "1.3.6.1.6.3.10.2.1.2";
      }

      leaf snmpEngineTime {
         type int32 {
            range "0..2147483647";
         }
         units "seconds";
         description
           "The number of seconds since the value of
            the snmpEngineBoots object last changed.
            When incrementing this object's value would
            cause it to exceed its maximum,
            snmpEngineBoots is incremented as if a
            re-initialization had occurred, and this
            object's value consequently reverts to zero.";
         smi:oid "1.3.6.1.6.3.10.2.1.3";
      }

      leaf snmpEngineMaxMessageSize {
         type int32 {
            range "484..2147483647";
         }
         description
           "The maximum length in octets of an SNMP message
            which this SNMP engine can send or receive and
            process, determined as the minimum of the maximum
            message size values supported among all of the
            transports available to and supported by the engine.";
         smi:oid "1.3.6.1.6.3.10.2.1.4";
      }
      smi:oid "1.3.6.1.6.3.10.2.1";
   }

} /* end of module SNMP-FRAMEWORK-MIB */
