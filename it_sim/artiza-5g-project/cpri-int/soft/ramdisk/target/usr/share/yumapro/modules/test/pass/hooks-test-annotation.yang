module hooks-test-annotation {
  namespace "http://netconfcentral.org/ns/hooks-test-annotation";
  prefix "hooks-ann";

  import hooks-test { prefix hk; }
  import hooktest { prefix hook; }
  import yuma-ncx { prefix ncx; }

  revision 2018-07-12 {
    description
      "Initial version";
  }

  deviation /hk:interfaces/hk:interface/hook:qos-cfg {
    deviate add {
      ncx:sil-delete-children-first;
    }
  }

}
