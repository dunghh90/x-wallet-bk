module testr1 {

    namespace "http://netconfcentral.org/ns/testr1";
    prefix "r1";

    import testr2 {
        prefix r2;
        revision-date 2008-01-01;
    }

    organization
        "Netconf Central";

    contact
        "Andy Bierman";

    description
        "YANG import-by-revision test module.";

    revision 2009-01-01 {
        description "Initial version.";
    }

    grouping TestGroup1 {
       leaf X { type string; }
       leaf Y { type leafref { path "../X"; } }
       uses r2:TestGroup;
    }

    container bar-r1 {
       uses r2:TestGroup;
    }

    container foo-r2 {
       uses r2:TestGroup;
    }
}
