module test-1 {
    namespace "http://netconfcentral.org/ns/test-1";
    prefix "test1";
    revision "2016-06-03";

    container stuff {
      leaf a { type string; }
      leaf b { type string; }
      leaf c { type string; }
    }
  }
