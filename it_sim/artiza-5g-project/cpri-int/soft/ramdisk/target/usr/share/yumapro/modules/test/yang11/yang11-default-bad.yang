module yang11-default-bad {

  yang-version 1.1;
  namespace "http://netconfcentral.org/ns/yang11-default-bad";
  prefix ydefbad;
  revision "2016-04-18" {
  }

  leaf-list def-bad-A {
    type int32 {}
    default 10;
    default 20;
    default 30;
    default 20;   // duplicate value in config
  }


  container top {
    presence "prevent mandatory top node error";

    leaf-list def-bad-B {
      type string {}
      min-elements 2;
      default fred;    // min-elements and default set
      default barney;
    }
  }

}
