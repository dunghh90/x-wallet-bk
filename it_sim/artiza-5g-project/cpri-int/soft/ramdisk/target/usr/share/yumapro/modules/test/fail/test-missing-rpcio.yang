module test-missing-rpcio {

  namespace "http://netconfcentral.org/ns/test-missing-rpcio";

  prefix trpcio;

  revision "2016-04-16" {
  }

  rpc bad-rpc {
    input {  }
    output {  }
  }

  rpc bad-rpc2 {
    input;
    output;
  }


}
